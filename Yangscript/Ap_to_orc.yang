module Ap_to_orc{
	namespace "https://Ap.com/Ap_to_orc";
	prefix "Ap_to_orc";
	
	typedef ipv4-address{
          type string{
          pattern
             '(([0-9]|[1-9][0-9]|1[0-9][0-9]|2[0-4][0-9]|25[0-5])\.){3}'
           +  '([0-9]|[1-9][0-9]|1[0-9][0-9]|2[0-4][0-9]|25[0-5])'
           + '(%[\p{N}\p{L}]+)?';
        	}
	}
	typedef mac-address {
       	  type string {
              pattern '[0-9a-fA-F]{2}(:[0-9a-fA-F]{2}){5}';
                }
	}	
	typedef throughput{
          type decimal64{
		fraction-digits 2;
             	range "1 .. 3.14 | 10 | 20..max";
		}
	}
	typedef Signal{
          type decimal64{
		fraction-digits 2;
             	range "1 .. 3.14 | 10 | 20..max";
		}
	}
	grouping client_one{
		list clients{
		key "mac-address";
		leaf mac{
			type mac-address;
			}
		leaf ip{
			type ipv4-address;
			}
		leaf throughput{
			type decimal64;
			}
		leaf Signal{
			type Signal;
			}
		}
	}
	container ApMac{
			uses client_one;
			}
	}
