module client_to_orc{
	namespace "https://client.com/client_to_orc";
	prefix "client_to_orc";

	typedef mac-address {
       	  type string {
              pattern '[0-9a-fA-F]{2}(:[0-9a-fA-F]{2}){5}';
                }
	}

	typedef ipv4-address{
          type string{
          pattern
             '(([0-9]|[1-9][0-9]|1[0-9][0-9]|2[0-4][0-9]|25[0-5])\.){3}'
           +  '([0-9]|[1-9][0-9]|1[0-9][0-9]|2[0-4][0-9]|25[0-5])'
           + '(%[\p{N}\p{L}]+)?';
        	}
	}
	typedef port-number{
	  type uint16{
		range "0..65535";
		}
	}
	typedef my-decimal {
         type decimal64 {
             fraction-digits 2;
             range "1 .. 3.14 | 10 | 20..max";
        	}
     	}

	grouping Aps{
		list Aps{
		key "Apmac";
		leaf Apmac{
			type mac-address;
			}
		leaf signal{
			type my-decimal;
			}
		}
	}
	
	
	grouping flows{
		list flows{
		key "ip_src";
		leaf ip_src{
			type ipv4-address;
			}
		leaf ip_dst{
			type ipv4-address;
			}
		leaf port{
			type port-number;
			}
		list Aps{
		key "Apmac";
		leaf Apmac{
			type mac-address;
			}
		leaf throughput{
			type my-decimal;
				}
			}
		}
	}
	container ClientMac{
		uses Aps;
		uses flows;
		}
}
