module orc_to_client{
	namespace "https://client.com/orc_to_client";
	prefix "orc_to_client";
	
	
	typedef mac-address {
       	  type string {
              pattern '[0-9a-fA-F]{2}(:[0-9a-fA-F]{2}){5}';
                }
	}

	typedef ipv4-address{
          type string{
          pattern
             '(([0-9]|[1-9][0-9]|1[0-9][0-9]|2[0-4][0-9]|25[0-5])\.){3}'
           +  '([0-9]|[1-9][0-9]|1[0-9][0-9]|2[0-4][0-9]|25[0-5])'
           + '(%[\p{N}\p{L}]+)?';
        	}
	}
	typedef port-number{
	  type uint16{
		range "0..65535";
		}
	}
	typedef my-decimal {
         type decimal64 {
             fraction-digits 2;
             range "1 .. 3.14 | 10 | 20..max";
        	}
     	}

	grouping handover{
		leaf mac-add{
			type mac-address;
			}
		leaf ap_mac_old{
			type mac-address;
			}
		leaf ap_mac_new{
			type mac-address;
			}
		}
	grouping loadbalance{
		leaf ip_src{
			type ipv4-address;
			}
		leaf ip_dst{
			type ipv4-address;
			}
		leaf port{
			type port-number;
			}
		list Aps{
		key "Apmac";
		leaf Apmac{
			type mac-address;
			}
		leaf weight{
			type my-decimal;
				}
			}
	}
	grouping duplication{
		leaf ip_src{
			type ipv4-address;
			}
		leaf ip_dst{
			type ipv4-address;
			}
		leaf port{
			type port-number;
			}
		list Aps{
		key "Apmac";
		leaf Apmac{
			type mac-address;
			}
		}
	}
	container Handover{
	   list mac{
		key "mac-add";
			uses handover;
		}
	}
	container Loadbalance{
           list flows{
		key "ip_src";
			uses loadbalance;
			}
	}
	container duplication{
	   list flows{
		key "ip_src";
		uses duplication;
		}
	}
}
