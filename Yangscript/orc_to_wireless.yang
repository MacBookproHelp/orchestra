module orc_to_wireless{
	namespace "https://wireless.com/orc_to_wireless";
	prefix "orc_to_wireless";
	
	typedef port-number{
	  type uint16{
		range "0..65535";
		}
	}
	typedef ipv4-address{
          type string{
          pattern
             '(([0-9]|[1-9][0-9]|1[0-9][0-9]|2[0-4][0-9]|25[0-5])\.){3}'
           +  '([0-9]|[1-9][0-9]|1[0-9][0-9]|2[0-4][0-9]|25[0-5])'
           + '(%[\p{N}\p{L}]+)?';
        	}
	}
	typedef mac-address {
       	  type string {
              pattern '[0-9a-fA-F]{2}(:[0-9a-fA-F]{2}){5}';
                }
	}
	grouping clients_one{
		leaf mac-address{
			type mac-address;
			}
		leaf old_mac{
			type mac-address;
			}
		leaf new_mac{
			type mac-address;
			}
	}
	container handover{
	    list client{
		// identify each client by its mac-address as key
		key "mac-address";
		uses clients_one;
		}
	}
}
