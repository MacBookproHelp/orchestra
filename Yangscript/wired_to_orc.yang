module wired_to_orc{
	namespace "https://wired.com/wired_to_orc";
	prefix "wired_to_orc";
	
	typedef port-number{
	  type uint16{
		range "0..65535";
		}
	}
	typedef ipv4-address{
          type string{
          pattern
             '(([0-9]|[1-9][0-9]|1[0-9][0-9]|2[0-4][0-9]|25[0-5])\.){3}'
           +  '([0-9]|[1-9][0-9]|1[0-9][0-9]|2[0-4][0-9]|25[0-5])'
           + '(%[\p{N}\p{L}]+)?';
        	}
	}
	
	typedef throughput{
          type decimal64{
		fraction-digits 2;
             	range "1 .. 3.14 | 10 | 20..max";
		}
	}
	typedef mac-address {
       	  type string {
              pattern '[0-9a-fA-F]{2}(:[0-9a-fA-F]{2}){5}';
                }
	}
	
	grouping flows{
		list flow{
		key "port";
		leaf ip_src{
		type ipv4-address;
			}
		leaf ip_dst{
		type ipv4-address;
			}
		leaf port{
		type port-number;
			}
		leaf throughput{
		type throughput;
			}
		}
	}
	
	container ControllerMac{
		container Switches{
			container SwitchMac{
			}
			container flows{
			uses flows;
			}
		}
	}
}
